module external-id-allocation {

  namespace "http://example.com/external-id-allocation";
  prefix ext-id;

  import ietf-inet-types {
    prefix inet;
  }
  import tailf-common {
    prefix tailf;
  }
  import tailf-ncs {
    prefix ncs;
  }

  description
  "Example of a package that allocates values from an external system";

  revision 2017-01-01 {
    description
    "Initial revision.";
  }


    container external-id-allocation {
        description "External ID allocations";

        container create-kickers {
            presence true;
            uses ncs:service-data;
            ncs:servicepoint external-id-allocation-servicepoint;
        }

        leaf use-random {
            type boolean;
            default true;
            tailf:info "when set it will not allocate from external system, instead it will just create a random Integer, use for testing";
        }

        list request {
          key name;

          leaf name {
            type string;
          }

          leaf allocating-service {
            tailf:info "Instance identifier of service that owns resouce";
            type instance-identifier {
              require-instance false;
            }
          }

          leaf id {
            tailf:info "Request a specific id";
            type int32;
            default "-1";
          }

          tailf:action allocate {
            tailf:actionpoint external-id-allocation-action;
            input {
              leaf re-allocate {
                type empty;
              }
            }
            output {
              leaf result {
                type string;
              }
            }
          }
        }
        list response {
            key name;

            leaf name {
              type string;
            }
            config false;
            tailf:cdb-oper {
              tailf:persistent true;
            }

            leaf allocating-service {
              tailf:info "Instance identifier of service that owns resource";
              type instance-identifier {
                require-instance false;
              }
            }

            choice response-choice {
              case error {
                leaf error {
                  type string;
                }
              }
              case ok {
                leaf id {
                  type uint32;
                }
              }
            }
            tailf:action re-deploy-service {
              tailf:actionpoint external-id-redeploy-action;
              output {
                leaf result {
                  type uint16;
                }
              }
            }
            tailf:action release {
              tailf:actionpoint external-id-release-action;
              input {
                leaf force-clean {
                    type empty;
                }
              }
              output {
                leaf result {
                  type uint16;
                }
              }
            }
        }
    }
}
